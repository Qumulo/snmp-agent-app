QUMULO-MIB DEFINITIONS ::= BEGIN

IMPORTS
       MODULE-IDENTITY, OBJECT-TYPE, Integer32, NOTIFICATION-TYPE, enterprises
                     FROM SNMPv2-SMI
;



qumuloModule MODULE-IDENTITY
    LAST-UPDATED "201906130000Z"
    ORGANIZATION "www.qumulo.com"
    CONTACT-INFO
	 "postal:   Mike Bott
                    1501 4th Ave, Ste 1600
                    Seattle WA 98101

          email:    mike@qumulo.com"
    DESCRIPTION
	"Updated module identity"
    REVISION     "201906130000Z"
    DESCRIPTION
	"Qumulo MIB objects for SNMP agent module"
    REVISION     "200406150000Z"
    DESCRIPTION
	"Corrected notification example definitions"
    REVISION     "200202060000Z"
    DESCRIPTION
	"First draft"
    ::= { 47017 2 }

myCompany OBJECT IDENTIFIER ::= {enterprises 47017 }

testCount OBJECT-TYPE
    SYNTAX Integer32
    MAX-ACCESS read-only
    STATUS current
    DESCRIPTION "My sample count of something."
    ::= {myCompany 1}

testDescription OBJECT-TYPE
    SYNTAX OCTET STRING
    MAX-ACCESS read-only
    STATUS current
    DESCRIPTION "My description of something"
    ::= {myCompany 2}

nodeDownTrap NOTIFICATION-TYPE
    STATUS current
    DESCRIPTION "Cluster Node Down Notification"
    ::= {myCompany 3}

driveFailureTrap NOTIFICATION-TYPE
    STATUS current
    DESCRIPTION "Cluster Node Down Notification"
    ::= {myCompany 4}

nodesClearTrap NOTIFICATION-TYPE
    STATUS current
    DESCRIPTION "Cluster Normal Notification"
    ::= {myCompany 5}

clusterUnreachableTrap NOTIFICATION-TYPE
    STATUS current
    DESCRIPTION "Cluster unreachable via REST API"
    ::= {myCompany 6}

powerSupplyFailureTrap NOTIFICATION-TYPE
    STATUS current
    DESCRIPTION "Power supply failure Notification"
    ::= {myCompany 7}

nodeName OBJECT-TYPE
    SYNTAX OCTET STRING
    MAX-ACCESS read-only
    STATUS current
    DESCRIPTION "Name of node for trap messages"
    ::= {myCompany 8}

driveId OBJECT-TYPE
    SYNTAX OCTET STRING
    MAX-ACCESS read-only
    STATUS current
    DESCRIPTION "Id of drive for trap messages"
    ::= {myCompany 9}

clusterName OBJECT-TYPE
    SYNTAX OCTET STRING
    MAX-ACCESS read-only
    STATUS current
    DESCRIPTION "Name of node for trap messages"
    ::= {myCompany 10}

powerSupplyId OBJECT-TYPE
    SYNTAX OCTET STRING
    MAX-ACCESS read-only
    STATUS current
    DESCRIPTION "ID of power supply for trap messages"
    ::= {myCompany 11}

END
