MY-MIB DEFINITIONS ::= BEGIN

IMPORTS
        OBJECT-TYPE, Integer32, NOTIFICATION-TYPE, enterprises
                     FROM SNMPv2-SMI
;

myCompany       OBJECT IDENTIFIER ::= {enterprises 43}

testCount OBJECT-TYPE
    SYNTAX Integer32
    MAX-ACCESS read-only
    STATUS current
    DESCRIPTION "My sample count of something."
    ::= {myCompany 1}

testDescription OBJECT-TYPE
    SYNTAX OCTET STRING
    MAX-ACCESS read-only
    STATUS current
    DESCRIPTION "My description of something"
    ::= {myCompany 2}

nodeDownTrap NOTIFICATION-TYPE
    STATUS current
    DESCRIPTION "Cluster Node Down Notification"
    ::= {myCompany 3}

nodesClearTrap NOTIFICATION-TYPE
    STATUS current
    DESCRIPTION "Cluster All Nodes Up Notification"
    ::= {myCompany 4}


nodeName OBJECT-TYPE
    SYNTAX DisplayString (SIZE (0..255))
    ACCESS read-only
    STATUS current
    DESCRIPTION "Name of node for trap messages"
    ::= {myCompany 5}

END
